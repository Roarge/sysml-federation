package <SF> Federation_Core {
    doc /* The demo: the SysML v2 adapter, the example stack behind it and the
           image they ship in. The pipeline the example describes is a different
           thing and is modelled in examples/pipeline/model.sysml. Every
           identifier of the light scheme (US-nn, SR-nn, SC-nn, AD-nnnn) is a
           short name here. See model/README.md. */
    private import VSE_Library::*;
    private import Federation_Library::*;
    private import Federation_Stakeholders::*;
    private import Federation_Domain::*;
    private import Federation_InterfaceTypes::*;
    private import Federation_Context::*;
    private import Federation_Concerns::*;
    private import Federation_StakeholderStories::*;
    private import Federation_SystemStories::*;
    private import Federation_DesignConstraints::*;
    private import Federation_UseCases::*;
    private import Federation_FunctionalArchitecture::*;
    private import Federation_LogicalArchitecture::*;
    private import Federation_VerificationCases::*;
    private import Federation_ValidationCases::*;
    private import Federation_Views::*;
    private import Federation_CheckCases::*;
}
